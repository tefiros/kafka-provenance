module insa-custom2 {
    yang-version 1;
    namespace "urn:ietf:params:xml:ns:yang:insa-yang";
    prefix iny;

    contact "alex.huang-feng@insa-lyon.fr";
    organization "INSA Lyon";
    description "insa-custom yang module";

    revision 2019-09-09 {
        description "Initial version.";
    }

    container insa-container {
        config false;
        leaf computer {
            type string;
            description "computer";
        }
        leaf router {
            type uint8;
            description "router";
        }
    }
}
