module ietf-telemetry-message {
  yang-version 1.1;
  namespace "urn:ietf:params:xml:ns:yang:telemetry-message";
  prefix tm;

  import ietf-yang-types {
    prefix yang;
  }
  import ietf-inet-types {
    prefix inet;
  }
  import ietf-platform-manifest {
    prefix p-mf;
    reference
      "draft-ietf-opsawg-collected-data-manifest: A Data Manifest for
      Contextualized Telemetry Data";
  }

  organization
    "IETF Draft";
  contact
    "Author:    Ahmed Elhassany
                <mailto:ahmed.elhassany@swisscom.com>

                Thomas Graf
                <mailto:thomas.graf@swisscom.com>";
  description
    "This YANG modules defines a model for a telemetry collector to send
     collected YANG data from the network.

     Copyright (c) 2025 IETF Trust and the persons identified as
       authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2025-04-12 {
    description
      "Initial revision.";
    reference
      "RFC XXXX";
  }

  typedef telemetry-notification-event-type {
    type enumeration {
      enum "log" {
        description
          "Collector is reporting the event as it arrived from the
          network element.";
      }
      enum "update" {
        description
          "
           Collector has updated an entry inside its local cache.
           This could be triggered by an event from the network for
           instance interface operational status changed or an internal
           event in the collector, such as a timer triggered to referesh
           old enteries.";
      }
      enum "delete" {
        description
          "Collector has deleted an entry from its local cache.";
      }
    }
    description
      "Type of event reported by the collector.";
  }

  typedef telemetry-notification-protocol-type {
    type enumeration {
      enum "netconf" {
        description
          "NETCONF RFC 8640.";
      }
      enum "restconf" {
        description
          "RESTCONF RFC 8650.";
      }
      enum "yp-configured" {
        description
          "YANG-Push Configured Subscription.";
      }
      enum "yp-dynamic" {
        description
          "YANG-Push Dynamic Subscription.";
      }
    }
    description
      "Notification protocol used to deliver the notification to the
      data collection.";
  }

  typedef telemetry-transport-protocol-type {
    type enumeration {
      enum "ssh" {
        description
          "SSH RFC 4253. Being used as transport in NETCONF RFC 8640.";
      }
      enum "http" {
        description
          "HTTP RFC 7231. Being used as transport in RESTCONF
          RFC 8650.";
      }
      enum "udp-notif" {
        description
          "draft-ietf-netconf-udp-notif, Being used as transport in
          YANG-Push Configured Subscription.";
      }
      enum "https-notif" {
        description
          "draft-ietf-netconf-https-notif, Being used as transport in
          YANG-Push Configured Subscription.";
      }
    }
    description
      "Transport protocol used to deliver the notification to the
      data collection.";
  }

  container notification {
    config false;
    leaf timestamp {
      type yang:date-and-time;
      mandatory true;
      description
        "Timestamp when the data collection received the notification
        from the network element or an update or delete event is
        triggered.";
    }
    leaf notification-protocol {
      type telemetry-notification-protocol-type;
      mandatory true;
      description
        "Notification protocol used to send the notification from
        network node to the data collection.";
    }
    leaf transport-protocol {
      type telemetry-transport-protocol-type;
      mandatory true;
      description
        "Transport protocol used to send the notification from network
        node to the data collection.";
    }
    container network-node-manifest {
      description
        "Address of network element sent the notification.";
      uses p-mf:platform-details;
    }
    container data-collection-manifest {
      description
        "Address of the telemetry data collection.";
      uses p-mf:platform-details;
    }
    container telemetry-notification-metadata {
      leaf event-time {
        type yang:date-and-time;
        mandatory true;
        description
          "NETCONF eventTime. Redefined in here since NETCONF header is
          XML not YANG.";
      }
    }
    container data-collection-metadata {
      description
        "Metadata added by data collection.";
      leaf remote-address {
        type inet:host;
        mandatory true;
        description
          "Network node IP address.";
      }
      leaf remote-port {
        type inet:port-number;
        description
          "Network node transport port number.";
      }
      leaf local-address {
        type inet:host;
        description
          "Data collection IP address.";
      }
      leaf local-port {
        type inet:port-number;
        description
          "Data collection transport port number.";
      }			
      list labels {
        key "name";
        description
          "Arbiterary labels assinged by the data collection.";
        leaf name {
          type string {
            length "1..max";
          }
          description
            "Label name.";
        }
        choice value {
          mandatory true;
          choice string-value {
            leaf string-values {
              type string;
            }
          }
          choice anydata-value {
            anydata anydata-values {
              description
                "anydata yang";
            }
          }
        }
      }
    }
    anydata payload {
      description
        "Notification received from network element.";
    }
  }
}
